Context-sdltype DEFINITIONS ::=
BEGIN
   IMPORTS
      T-INTEGER FROM DataView;

--  Group all context parameters of this function in a record
Context-sdltype ::= SEQUENCE {
   foo T-INTEGER

}

--  Declare a constant with the values set by the user in the interface view
sdltype-ctxt Context-sdltype ::= {
   foo 42

}
END
